TASTE-Dataview DEFINITIONS ::=
BEGIN
IMPORTS T-Int32, T-UInt32, T-Int8, T-UInt8, T-Boolean FROM TASTE-BasicTypes;

-- A few simple types related to the FMI 2.0 standard - The fmi2String has max length of 255 characters. 
FmiInteger      ::= T-Int32

FmiReal         ::= REAL (-1000.0 .. 1000.0)

FmiBoolean      ::= BOOLEAN

FmiString       ::= OCTET STRING (SIZE (0..255))

END
